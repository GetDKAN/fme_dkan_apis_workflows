FME workspace dkan_dataset_api_test.fmw
Shutdown Python:
      import fme
      import os
      import json
      from dkan.client import DatasetAPI

      DKAN_URI = 'http://docker:32776'
      RESOURCE_ID = 5
      CSV = '%s/CSV.csv' % fme.macroValues['DestDataset_CSV']
      DKAN_USER = 'admin'
      DKAN_PASSWORD = 'admin'

      # Make the api authenticate properly
      api = DatasetAPI(DKAN_URI, DKAN_USER, DKAN_PASSWORD, True)

      # Get the resource node which file we want to update
      resource = api.node(RESOURCE_ID, 'retrieve')
      resource = resource.json()

      # Check if the field for the file is empty.
      if type(resource['field_upload']) != list:
        # If it's not empty, then clear the field
        data = {
          'field_upload': {
            'und': [{}],
          },
        }
        data = json.dumps(data)
        r = api.node(RESOURCE_ID, 'update', data=data)
        print r.status_code
        print r.text

      # Attach the file to the resource node
      r = api.attach_file_to_node(CSV, RESOURCE_ID)
      print r.status_code
      print r. text

Parameters:
- DestDataset_CSV = /Users/teofilosibileau/Downloads   # Destination CSV (Comma Separated Value) Folder

Readers:
- GOOGLESHEETS_1: GOOGLESHEETS

Writers:
- CSV_1: CSV to $(DestDataset_CSV)

Sheet1 (reader GOOGLESHEETS_1)
    attributes: Name text, Team text, Latitude text, Longitude text
    -> PythonModuleInstaller
PythonModuleInstaller
    TRY_IMPORT = No
    PYTHON_MODULES = git+git://github.com/NuCivic/pydkan.git@0.1#egg=pydkan
    -> CSV (writer CSV_1)
CSV (writer CSV_1)
    attributes: Name text, Team text, Latitude text, Longitude text

FME custom transformer PythonModuleInstaller
This custom transformer will automatically check and download python modules (packages) from PyPi, at https://pypi.python.org/pypi.
Place the transformer somewhere along the pipeline before the PythonCaller that requires it. Enter the required python modules as a comma-separated list. Useful for including in other custom transformers so that they can be distributed. Will not download anything unless python modules or setuptools are missing.
If you incorporate this transformer into a custom transformer for distribution in the FME Store, you should place the following text in the description of that transformer:
    This transformer makes use of the PythonModuleInstaller to manage Python module dependencies. It will automatically install setuptools from [1]. You can read more about setuptools, including its license terms, at [2]. It will then connect to PyPi [3] and install the following modules: <list of your Python dependencies here>.
    [1] https://bootstrap.pypa.io/ez_setup.py
    [2] https://pypi.python.org/pypi/setuptools
    [3] https://pypi.python.org/pypi
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- PYTHON_MODULES =   # Comma-separated list of python modules
- TRY_IMPORT = Yes   # Try importing modules (may fail)

Input (input)
    -> Sampler
Sampler
    SAMPLE_TYPE_LONG = First N Features
    RATE = 1
    SAMPLED -> PythonCaller_2
    NOT_SAMPLED -> VariableRetriever
PythonCaller_2
    NEW_ATTRIBUTES = pmi_setuptools_not_imported
    PYTHONSOURCE:
      import fmeobjects, imp
      # Template Function interface:
      def processFeature(feature):
          try:
              import setuptools
          except ImportError as e:
              feature.setAttribute("pmi_setuptools_not_imported", True)
    PYTHONSYMBOL = processFeature
    -> Tester
Tester
    TEST_MODE = Automatic
    TEST_CLAUSE = TEST @Value(pmi_setuptools_not_imported) = Yes
    BOOL_OP = OR
    TEST_DESCRIPTION = ""
    PASSED -> HTTPFetcher
    FAILED -> ParameterFetcher
Tester_2
    TEST_MODE = Automatic
    TEST_CLAUSE = TEST @Value(pmi_message) NOT_CONTAINS ERROR
    BOOL_OP = OR
    TEST_DESCRIPTION = ""
    PASSED -> AttributeRemover_2
    FAILED -> VariableSetter
VariableSetter
    VALUE = Yes
    SCOPE = Global
    VARNAME = pmi_is_error
    -> AttributeRemover
AttributeRemover
    LIST_ATTRS = _headers{}.value _headers{}.name _headers{}
    -> <Error> (output)
<Error> (output)
VariableRetriever
    SCOPE = Global
    VALUE_ATTR = pmi_is_error
    VARNAME = pmi_is_error
    -> Tester_3
Tester_3
    TEST_MODE = Automatic
    TEST_CLAUSE = TEST @Value(pmi_is_error) NOT_= Yes
    BOOL_OP = OR
    TEST_DESCRIPTION = ""
    PASSED -> AttributeRemover_2
AttributeRemover_2
    REMOVE_ATTRS = pmi_is_error,pmi_setuptools_not_imported,_error,_http_status_code,_url_contents,pmi_python_modules_to_install,pmi_mod_install_fail,pmi_message
    LIST_ATTRS = pmi_modules_installed{} _headers{}.value _headers{}.name _headers{}
    -> Output (output)
Output (output)

Bookmark: Install setuptools
HTTPFetcher
    TARGET_ATTR = _url_contents
    STATUS_CODE_ATTR = _http_status_code
    TARGET_URL = https://bootstrap.pypa.io/ez_setup.py
    OUTPUT_FILENAME = ez_setup.py
    FOLLOW_REDIRECTS = Yes
    PROXY_AUTH_METHOD = Basic
    SAVE_FILE = Yes
    VERIFY_SSL_CERTIFICATES = Yes
    USE_COOKIES = No
    ERROR_ATTR = _error
    RESPONSE_HEADER_LIST_ATTR = _headers
    AUTH_METHOD = Basic
    -> PythonCaller
PythonCaller
    PYTHONSOURCE:
      import fmeobjects, os, site, glob, sys

      # Template Function interface:
      def processFeature(feature):
          try:
              import ez_setup
              ez_setup.main()
              mysp = [x for x in site.getsitepackages() if x[-13:] == "site-packages"][0]
              newpath = glob.glob(mysp + "/setuptools*.egg")
              sys.path += newpath
          except Exception as e:
              raise e
          finally:
              os.remove(ez_setup.__file__)
              os.remove(ez_setup.__file__+'c')
    PYTHONSYMBOL = processFeature
    -> ParameterFetcher

Bookmark: Install packages
ParameterFetcher
    ATTR_LIST = pmi_python_modules_to_install {$(PYTHON_MODULES)} _tryImport {$(TRY_IMPORT)} _FME_JOB_ID {$(FME_JOB_ID)}
    -> PythonCaller_3
PythonCaller_3
    NEW_ATTRIBUTES = pmi_mod_install_fail pmi_modules_installed{} pmi_message
    PYTHONSOURCE:
      import fmeobjects, importlib, sys, imp, site
      # Template Function interface:
      def processFeature(feature):

          logger = fmeobjects.FMELogFile()

          from setuptools.command import easy_install

          mods = feature.getAttribute("pmi_python_modules_to_install")
          mods = str(mods).split(",")

          modsNotPresent = []
          for mod in mods:
              try:
                  importlib.import_module(mod)
              except ImportError:
                  modsNotPresent.append(mod)
          if not modsNotPresent == []:
              try:
                  if feature.getAttribute("_FME_JOB_ID") == '':
                      easy_install.main(["--user"] + modsNotPresent)
                  else:
                      easy_install.main(["-d", FME_MacroValues['FME_SHAREDRESOURCE_ENGINE'] + '/Plugins/python/python27'] + modsNotPresent)
                  feature.setAttribute("pmi_modules_installed", modsNotPresent)
                  feature.setAttribute("pmi_message", "WARNING: New Python modules were installed.")

                  reload(site)

                  if feature.getAttribute("_tryImport") == "Yes":
                      for mod in modsNotPresent:
                          exec("import "+mod)


              except Exception as e:
                  feature.setAttribute("pmi_mod_install_fail", True)
                  feature.setAttribute("pmi_message", "ERROR: Python modules were not successfully installed. Exception: " + str(e))

              finally:
                  logger.logMessageString(feature.getAttribute("pmi_message"),fmeobjects.FME_ERROR)
    PYTHONSYMBOL = processFeature
    -> Tester_2

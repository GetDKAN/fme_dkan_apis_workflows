FME workspace attach_file_to_node.fmw
Title: attach_file_to_resource
Shutdown Python:
      import fme
      import os
      import json
      from dkan.client import DatasetAPI

      # Set PYDKAN PARAMETERS from fme's USER PARAMETERS
      DKAN_URI = fme.macroValues['DKAN_URI']
      RESOURCE_ID = fme.macroValues['DKAN_RESOURCE_ID']
      CSV = '%s/CSV.csv' % fme.macroValues['DestDataset_CSV']
      DKAN_USER = fme.macroValues['DKAN_USER']
      DKAN_PASSWORD = fme.macroValues['DKAN_PASSWORD']

      # Make the api authenticate properly
      api = DatasetAPI(DKAN_URI, DKAN_USER, DKAN_PASSWORD, True)
      # Attach the file to the resource node
      r = api.attach_file_to_node(CSV, RESOURCE_ID, 'field_upload')

      print r.status_code
      print r.text

Parameters:
- DestDataset_CSV = output   # Destination CSV (Comma Separated Value) Folder
- DKAN_URI = http://docker:32770   # DKAN URL
- DKAN_RESOURCE_ID = 34   # DKAN Resource ID
- DKAN_USER = admin   # DKAN User Name
- DKAN_PASSWORD =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   # DKAN User Password
- SourceDataset_CSV = data/premier_league_stadiums.csv   # Source CSV (Comma Separated Value) File(s)

Readers:
- CSV_2: CSV from $(SourceDataset_CSV)

Writers:
- CSV_1: CSV to $(DestDataset_CSV)

CSV (reader CSV_2)
    attributes: Name char(27), Team char(21), Capacity number(6,0), Address char(76)
    -> InstallPyDKAN
InstallPyDKAN: PythonModuleInstaller
    PYTHON_MODULES = git+git://github.com/NuCivic/pydkan.git#egg=pydkan
    TRY_IMPORT = No
    -> CSV (writer CSV_1)
CSV (writer CSV_1)
    attributes: Name text, Team text, Capacity text, Address char(76)

FME custom transformer PythonModuleInstaller
This custom transformer will automatically check and download python modules (packages) from PyPi, at https://pypi.python.org/pypi.
Place the transformer somewhere along the pipeline before the PythonCaller that requires it. Enter the required python modules as a comma-separated list. Useful for including in other custom transformers so that they can be distributed. Will not download anything unless python modules or setuptools are missing.
If you incorporate this transformer into a custom transformer for distribution in the FME Store, you should place the following text in the description of that transformer:
    This transformer makes use of the PythonModuleInstaller to manage Python module dependencies. It will automatically install setuptools from [1]. You can read more about setuptools, including its license terms, at [2]. It will then connect to PyPi [3] and install the following modules: <list of your Python dependencies here>.
    [1] https://bootstrap.pypa.io/ez_setup.py
    [2] https://pypi.python.org/pypi/setuptools
    [3] https://pypi.python.org/pypi
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- PYTHON_MODULES =   # Comma-separated list of python modules
- TRY_IMPORT = Yes   # Try importing modules (may fail)

Input (input)
    -> Sampler
Sampler
    SAMPLE_TYPE_LONG = First N Features
    RATE = 1
    SAMPLED -> PythonCaller_2
    NOT_SAMPLED -> VariableRetriever
PythonCaller_2
    PYTHONSYMBOL = processFeature
    PYTHONSOURCE:
      import fmeobjects, imp
      # Template Function interface:
      def processFeature(feature):
          try:
              import setuptools
          except ImportError as e:
              feature.setAttribute("pmi_setuptools_not_imported", True)
    NEW_ATTRIBUTES = pmi_setuptools_not_imported
    -> Tester
Tester
    BOOL_OP = OR
    TEST_CLAUSE = TEST @Value(pmi_setuptools_not_imported) = Yes
    TEST_MODE = Automatic
    TEST_DESCRIPTION = ""
    PASSED -> HTTPFetcher
    FAILED -> ParameterFetcher
Tester_2
    BOOL_OP = OR
    TEST_CLAUSE = TEST @Value(pmi_message) NOT_CONTAINS ERROR
    TEST_MODE = Automatic
    TEST_DESCRIPTION = ""
    PASSED -> AttributeRemover_2
    FAILED -> VariableSetter
VariableSetter
    VALUE = Yes
    SCOPE = Global
    VARNAME = pmi_is_error
    -> AttributeRemover
AttributeRemover
    LIST_ATTRS = _headers{}.value _headers{}.name _headers{}
    -> <Error> (output)
<Error> (output)
VariableRetriever
    SCOPE = Global
    VARNAME = pmi_is_error
    VALUE_ATTR = pmi_is_error
    -> Tester_3
Tester_3
    BOOL_OP = OR
    TEST_CLAUSE = TEST @Value(pmi_is_error) NOT_= Yes
    TEST_MODE = Automatic
    TEST_DESCRIPTION = ""
    PASSED -> AttributeRemover_2
AttributeRemover_2
    LIST_ATTRS = pmi_modules_installed{} _headers{}.value _headers{}.name _headers{}
    REMOVE_ATTRS = pmi_is_error,pmi_setuptools_not_imported,_error,_http_status_code,_url_contents,pmi_python_modules_to_install,pmi_mod_install_fail,pmi_message
    -> Output (output)
Output (output)

Bookmark: Install setuptools
HTTPFetcher
    AUTH_METHOD = Basic
    VERIFY_SSL_CERTIFICATES = Yes
    OUTPUT_FILENAME = ez_setup.py
    TARGET_ATTR = _url_contents
    PROXY_AUTH_METHOD = Basic
    FOLLOW_REDIRECTS = Yes
    TARGET_URL = https://bootstrap.pypa.io/ez_setup.py
    USE_COOKIES = No
    SAVE_FILE = Yes
    ERROR_ATTR = _error
    STATUS_CODE_ATTR = _http_status_code
    RESPONSE_HEADER_LIST_ATTR = _headers
    -> PythonCaller
PythonCaller
    PYTHONSYMBOL = processFeature
    PYTHONSOURCE:
      import fmeobjects, os, site, glob, sys

      # Template Function interface:
      def processFeature(feature):
          try:
              import ez_setup
              ez_setup.main()
              mysp = [x for x in site.getsitepackages() if x[-13:] == "site-packages"][0]
              newpath = glob.glob(mysp + "/setuptools*.egg")
              sys.path += newpath
          except Exception as e:
              raise e
          finally:
              os.remove(ez_setup.__file__)
              os.remove(ez_setup.__file__+'c')
    -> ParameterFetcher

Bookmark: Install packages
ParameterFetcher
    ATTR_LIST = pmi_python_modules_to_install {$(PYTHON_MODULES)} _tryImport {$(TRY_IMPORT)} _FME_JOB_ID {$(FME_JOB_ID)}
    -> PythonCaller_3
PythonCaller_3
    PYTHONSYMBOL = processFeature
    PYTHONSOURCE:
      import fmeobjects, importlib, sys, imp, site
      # Template Function interface:
      def processFeature(feature):

          logger = fmeobjects.FMELogFile()

          from setuptools.command import easy_install

          mods = feature.getAttribute("pmi_python_modules_to_install")
          mods = str(mods).split(",")

          modsNotPresent = []
          for mod in mods:
              try:
                  importlib.import_module(mod)
              except ImportError:
                  modsNotPresent.append(mod)
          if not modsNotPresent == []:
              try:
                  if feature.getAttribute("_FME_JOB_ID") == '':
                      easy_install.main(["--user"] + modsNotPresent)
                  else:
                      easy_install.main(["-d", FME_MacroValues['FME_SHAREDRESOURCE_ENGINE'] + '/Plugins/python/python27'] + modsNotPresent)
                  feature.setAttribute("pmi_modules_installed", modsNotPresent)
                  feature.setAttribute("pmi_message", "WARNING: New Python modules were installed.")

                  reload(site)

                  if feature.getAttribute("_tryImport") == "Yes":
                      for mod in modsNotPresent:
                          exec("import "+mod)


              except Exception as e:
                  feature.setAttribute("pmi_mod_install_fail", True)
                  feature.setAttribute("pmi_message", "ERROR: Python modules were not successfully installed. Exception: " + str(e))

              finally:
                  logger.logMessageString(feature.getAttribute("pmi_message"),fmeobjects.FME_ERROR)
    NEW_ATTRIBUTES = pmi_mod_install_fail pmi_modules_installed{} pmi_message
    -> Tester_2
